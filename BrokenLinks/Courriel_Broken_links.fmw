FME workspace Courriel_Broken_links.fmw

Parameters:
- DestDataset_XLSXW_4 =   # Destination XLSX UUID sans contact
- SourceDataset_XLSXR =   # Source Mapping type problème xlsx
- ENV = STAGING
- Fme_Server_User_Name:   # Python Script
      if FME_MacroValues['ENV'] == 'DEV':
          return "sys_ddr-dev"
      elif FME_MacroValues['ENV'] == 'STAGING':
          return "sys_ddr-stage"
      elif FME_MacroValues['ENV'] == 'PROD':
          return "fgp-pgf"
- Fme_Server_Password_dev =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
- Fme_Server_Password_staging =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
- Fme_Server_Password_prod =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
- Fme_Server_Password:   # Python Script
      if FME_MacroValues['ENV'] == 'DEV':
          return FME_MacroValues['Fme_Server_Password_dev']
      elif FME_MacroValues['ENV'] == 'STAGING':
          return FME_MacroValues['Fme_Server_Password_staging']
      elif FME_MacroValues['ENV'] == 'PROD':
          return FME_MacroValues['Fme_Server_Password_prod']

Readers:
- XLSXR_1: XLSXR from $(SourceDataset_XLSXR)

Writers:
- XLSXW_1: XLSXW to $(DestDataset_XLSXW_4)

SQLExecutor_3
    COMBINE_ATTRS = Result Attributes Only
    COMBINE_GEOM = Initiator Geometry Only
    DATASET = FGP_data_AWS
    EXPOSED_ATTRIBUTE_LIST = broken_link_problem,broken_link_status,broken_link_status_date,date_email,juridiction,metadata_uuid,resource_format,url
    FORMAT = POSTGRES
    POSTGRES_CREATE_FEATURE_TABLES_FROM_DATA = Yes
    POSTGRES_NAMED_CONNECTION = BD_interne_test
    POSTGRES_QUERY_FEATURE_TYPES_FOR_MERGE_FILTERS = Yes
    POSTGRES_READ_TIME_WITH_TIMEZONE = Yes
    POSTGRES_SCHEMAS_FOR_TABLE_LISTING = broken_links
    SQL_STATEMENT:
      with table_temp AS (
      SELECT DISTINCT ON (broken_links_issues.metadata_uuid, broken_links_issues.url)
      broken_links_issues.metadata_uuid,
      broken_links_issues.url,
      broken_links_issues.broken_link_status_date,
      broken_links_issues.broken_link_status,
      broken_links_issues.date_email,
      broken_links_issues.resource_format,
      broken_links_issues.broken_link_problem,
      broken_links_issues.juridiction
      FROM broken_links.broken_links_issues
      ORDER BY broken_links_issues.metadata_uuid, broken_links_issues.url, broken_links_issues.broken_link_status_date DESC)
      SELECT * from table_temp WHERE broken_link_status='CONFIRMED' AND juridiction='Fed'
    RESULT -> VariableRetriever
VariableRetriever
    SCOPE = Global
    VALUE_ATTR = Datetime
    VARNAME = Datetime
    -> Tester_Courriel
Note: courriel déjà envoyé?
Tester_Courriel
    BOOL_OP = OR
    COMPOSITE_TEST = 1
    TEST_CLAUSE = TEST date_email ATTRIBUTE_HAS_A_VALUE ""
    TEST_MODE = TEST
    PASSED -> DateTimeConverter
    FAILED -> DuplicateFilter_2
DuplicateFilter_2
    INPUT_ORDERED_CHOICE = No
    KEYATTR = metadata_uuid url broken_link_problem broken_link_status broken_link_status_date resource_format
    UNIQUE -> AttributeRenamer_2
AttributeRenamer_2
    ATTR_TABLE = RENAME_SET_DEFAULT Datetime > date_email
    -> AttributeKeeper_3
AttributeKeeper_3
    KEEP_ATTRS = broken_link_problem,broken_link_status_date,metadata_uuid,resource_format,url,broken_link_status,date_email
    -> Catalogue_Reader
Catalogue_Reader: Catalogue Reader
    CKAN_FILTER = fq=collection:fgp
    CUSTOM_CSW_LIST_NAME = DefaultNoList{}
    IDENTIFIANT = @Value(metadata_uuid)
    SOURCE_URL = https://maps.canada.ca/geonetwork/srv/eng/csw?
    UUID_invalide -> Logger
    Résultats -> AttributeExposer_2
    MetadonnéesNonTrouvées -> Logger
Note: Metadata Contact - courriel / Data Contact - courriel / Metadata Title EN / Metadata Title FR
AttributeExposer_2
    ATTR_LIST = MD_Metadata.contact.CI_ResponsibleParty.contactInfo.CI_Contact.address.CI_Address.electronicMailAddress.CharacterString,MD_Metadata.contact.CI_ResponsibleParty{}.contactInfo.CI_Contact.address.CI_Address.electronicMailAddress.CharacterString,MD_Metadata.identificationInfo.MD_DataIdentification.citation.CI_Citation.title.CharacterString,MD_Metadata.identificationInfo.MD_DataIdentification.citation.CI_Citation.title.PT_FreeText.textGroup.LocalisedCharacterString,MD_Metadata.identificationInfo.MD_DataIdentification.citation.CI_Citation.citedResponsibleParty.CI_ResponsibleParty.contactInfo.CI_Contact.address.CI_Address.electronicMailAddress.CharacterString,MD_Metadata.identificationInfo.MD_DataIdentification.citation.CI_Citation.citedResponsibleParty{}.CI_ResponsibleParty.contactInfo.CI_Contact.address.CI_Address.electronicMailAddress.CharacterString
    -> ListConcatenator_4
Metadata_Contact: Tester
    BOOL_OP = OR
    COMPOSITE_TEST = 1
    TEST_CLAUSE = TEST _courriel ATTRIBUTE_HAS_A_VALUE ""
    TEST_MODE = TEST
    PASSED -> AttributeCreator_5
    FAILED -> ListConcatenator_3
Logger
    LOG_FEATURE = LOG_ONLY
    MAXCOORDS = 20
    MAXFEATS = 20
    MESSAGE = UUID invalide ou non présent dans le catalogue sélectionné
    SEVERITY = WARN
AttributeKeeper_2
    KEEP_ATTRS = Title,Titre,_courriel,broken_link_problem,broken_link_problem_fr,broken_link_status_date,metadata_uuid,resource_format,url,broken_link_problem_en,date_email,broken_link_status
    -> AttributeSplitter
Note: création des courriels par contributeurs
ListBuilder_courriel
    GROUP_BY = _courriel Destinataire date_email
    LIST_ATTRS_TO_INCLUDE = broken_link_problem broken_link_problem_fr metadata_uuid Title Titre url resource_format broken_link_status broken_link_status_date
    LIST_NAME = _list_Par_courriel
    -> FeatureMerger [REQUESTOR]
FeatureMerger
    ATTR_ACCUM_MODE = Merge Supplier
    ATTR_CONFLICT_RES = Use Requestor
    CLEANING_TOLERANCE = Automatic
    CONNECT_Z_MODE = First Wins
    GEOM_TYPE = Build Polygons
    IGNORE_NULLS = No
    JOIN_KEYS = 1 1 AUTO
    MERGE_TYPE = Attributes Only
    PROCESS_DUPS = YES
    REJECT_NULL_MISSING_KEYS = No
    SUPPLIERS_FIRST = No
    MERGED -> FMEServerEmailGenerator
Note: Génération courriels avec attachments
FMEServerEmailGenerator
    email_attachment_paths = $(FME_SHAREDRESOURCE_DATA)/Broken_Links/email/@Value(date_email)/@Value(Destinataire).csv
    email_bcc = nrcan.fgpcontributorssupport-pgfsupportcontributeurs.rncan@canada.ca
    email_subject = Broken Links in the metadata / Liens brisés dans les métadonnées
    email_subscriber_content:
      Le français suit…
      Hello,

      As part of our Quality approach, a Standard Operating Procedure has been established in order to automatically detect all the broken links in the resources section of the FGP metadata.
      The attached csv file contains a list of datasets that have inaccessible links to ressources:

      Thank you to take care of this problem and apply correction if necesssary.

      If the link is working, you have no knowledge of the mentioned dataset(s) or have trouble understanding the action to take, feel free to contact the FGP support mailbox:
      nrcan.fgpcontributorssupport-pgfsupportcontributeurs.rncan@canada.ca
      The FGP Data Team

      Bonjour,

      Dans le cadre de notre approche qualité, une procédure opérationnelle normalisée visant à détecter les liens brisés dans la section des ressources des métadonnées a été instaurée
      Le fichier csv en pièce jointe contient une liste de jeux de données comportant des liens non fonctionnels:

      Merci de prendre connaissance de la situation et de corriger le problème si nécessaire.

      Si le lien fonctionne, que vous n’êtes pas au courant de ce jeu de données ou si vous avez des difficultés à comprendre les correctifs qui vous sont demandés, vous pouvez communiquer avec l’équipe de support de la PGF :
      nrcan.fgpcontributorssupport-pgfsupportcontributeurs.rncan@canada.ca
      L’Équipe des données de la PGF
    email_to = @Value(_courriel)
    -> FMEServerNotifier_2
FMEServerNotifier_2
    BODY = @Value(text_line_data)
    PASSWORD = $(Fme_Server_Password)
    SERVER_NAME = $(FME_SERVER_WEB_URL)
    TOPIC = BrokenLinks_Send_Email_Topic
    USERNAME = $(Fme_Server_User_Name)
    -> ListExploder

Bookmark: Création d'un Datestamp pour nom unique du répertoire pour les attachments
Creator
    GEOMTYPE = Geometry Object
    NUM = 1
    CREATED -> DateTimeStamper
DateTimeStamper
    DATETIME_ATTR = _timestamp
    INCLUDE_OFFSET = NO
    STAMP_TYPE = datetime
    TIMEZONE = local
    -> AttributeSplitter_2
AttributeSplitter_2
    ATTR_NAME = _timestamp
    DELIMITER = .
    DROP_EMPTY_PARTS = No
    LIST_NAME = _list_datetime
    TRIM_OPTION = Both
    -> VariableSetter
VariableSetter
    SCOPE = Global
    VALUE = @Value(_list_datetime{0})
    VARNAME = Datetime
    -> SQLExecutor_3 [INITIATOR]

Bookmark: Calcul de l'intervalle depuis l'envoi du courriel afin de voir si un rappel est nécessaire
DateTimeConverter
    DATETIME_ATTR = Datetime
    OUT_FORMAT = %Y%m%d
    PASSTHROUGH = NO
    REPAIR_INPUT = YES
    -> DateTimeCalculator
DateTimeCalculator
    MODE = DATETIMECALC_3_CALCULATE_INTERVAL
    OPERATION_PARAMETERS = START_DATETIME]@Value(date_email)]END_DATETIME]@Value(Datetime)]RESULT_TYPE]DAYS]RESULT_INTERVAL]_jours_rappel]FME_CONTROLLER_QUERY_FILE]transformers/dependencies/datetimecalculator/DATETIMECALC_3_CALCULATE_INTERVAL.fme
    -> Tester_Rappel
Note: Plus de 90 jours?
Tester_Rappel
    BOOL_OP = OR
    COMPOSITE_TEST = 1
    TEST_CLAUSE = TEST @Value(_jours_rappel) > 90
    TEST_MODE = TEST
    PASSED -> DuplicateFilter_2

Bookmark: Metadata Contact Email
ListConcatenator_4
    DROP_EMPTY_PARTS = No
    LIST_ATTR = MD_Metadata.contact.CI_ResponsibleParty{}.contactInfo.CI_Contact.address.CI_Address.electronicMailAddress.CharacterString
    SEP = ;
    VAL_ATTR = _courriel
    -> Tester_4
Tester_4
    BOOL_OP = OR
    COMPOSITE_TEST = 1
    TEST_CLAUSE = TEST _courriel ATTRIBUTE_HAS_A_VALUE ""
    TEST_MODE = TEST
    PASSED -> Metadata_Contact
    FAILED -> AttributeCreator_4
AttributeCreator_4
    ATTR_TABLE = SET_TO _courriel = @Value(MD_Metadata.contact.CI_ResponsibleParty.contactInfo.CI_Contact.address.CI_Address.electronicMailAddress.CharacterString)
    -> Metadata_Contact

Bookmark: Data contact email (lorsque Metadata Contact n'a pas de courriel)
ListConcatenator_3
    DROP_EMPTY_PARTS = Yes
    LIST_ATTR = MD_Metadata.identificationInfo.MD_DataIdentification.citation.CI_Citation.citedResponsibleParty{}.CI_ResponsibleParty.contactInfo.CI_Contact.address.CI_Address.electronicMailAddress.CharacterString
    SEP = ;
    VAL_ATTR = _courriel
    -> Tester_3
Tester_3
    BOOL_OP = OR
    COMPOSITE_TEST = 1
    TEST_CLAUSE = TEST _courriel ATTRIBUTE_HAS_A_VALUE ""
    TEST_MODE = TEST
    PASSED -> Data_Contact
    FAILED -> AttributeCreator_6
AttributeCreator_6
    ATTR_TABLE = SET_TO _courriel = @Value(MD_Metadata.identificationInfo.MD_DataIdentification.citation.CI_Citation.citedResponsibleParty.CI_ResponsibleParty.contactInfo.CI_Contact.address.CI_Address.electronicMailAddress.CharacterString)
    -> Data_Contact
Data_Contact: Tester
    BOOL_OP = OR
    COMPOSITE_TEST = 1
    TEST_CLAUSE = TEST _courriel ATTRIBUTE_HAS_A_VALUE ""
    TEST_MODE = TEST
    PASSED -> AttributeCreator_5
    FAILED -> UUID_Sans_courriel (writer XLSXW_1)

Bookmark: Titre - Title
AttributeCreator_5
    ATTR_TABLE:
      SET_TO Title = @Value(MD_Metadata.identificationInfo.MD_DataIdentification.citation.CI_Citation.title.CharacterString)
      SET_TO Titre = @Value(MD_Metadata.identificationInfo.MD_DataIdentification.citation.CI_Citation.title.PT_FreeText.textGroup.LocalisedCharacterString)
      SET_TO broken_link_problem_en = @Value(broken_link_problem)
    -> METADATA_VALUE_MAPPER [DATA_INPUT]

Bookmark: Aucun courriel Contact (Metadata et Data)
UUID_Sans_courriel (writer XLSXW_1)
    attributes: metadata_uuid string(20), url string(80)

Bookmark: Ajout de la description pour les erreurs
Mapping_Problems_URL (reader XLSXR_1)
    attributes: original_value char(29), real_value_english char(51), real_value_french char(47)
    -> METADATA_VALUE_MAPPER [LOOKUP_TABLE_INPUT]
METADATA_VALUE_MAPPER
    ATT_TO_MAP = broken_link_problem
    CODE_REFRESH = NO
    ENGLISH_REFRESH = YES
    ERROR_NOT_MAPPED = YES
    FRENCH_REFRESH = YES
    -> AttributeExposer
AttributeExposer
    ATTR_LIST = broken_link_problem_fr
    -> AttributeKeeper_2

Bookmark: Création de l'attribut Destinataire
AttributeSplitter
    ATTR_NAME = _courriel
    DELIMITER = @
    DROP_EMPTY_PARTS = No
    LIST_NAME = _list_destinataire
    TRIM_OPTION = Both
    -> AttributeCreator_3
AttributeCreator_3
    ATTR_TABLE = SET_TO Destinataire = @Value(_list_destinataire{0})
    -> AttributeRenamer
    -> ListBuilder_courriel

Bookmark: Création des fichiers CSV pour pièces jointes dans répertoire avec Date
AttributeRenamer
    ATTR_TABLE:
      RENAME_SET_DEFAULT broken_link_problem_en > Problem
      RENAME_SET_DEFAULT broken_link_problem_fr > Problème
      RENAME_SET_DEFAULT metadata_uuid > Metadata_UUID
      RENAME_SET_DEFAULT resource_format > Format
    -> Sorter
Sorter
    SORT_PARM = Metadata_UUID ALPHA ASCENDING
    SORTED -> FeatureWriter [Output]
FeatureWriter
    CSV2_COORDINATE_SYSTEM_GRANULARITY = FEATURE_TYPE
    CSV2_DELIMITER = ,
    CSV2_ENCODING = UTF-8
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_WRITE_BOM_FOR_UNICODE = Yes
    CSV2_WRITE_FIELD_NAMES = firstrow
    CSV2_WRITE_SCHEMA_FILE = NO
    DATASET = $(FME_SHAREDRESOURCE_DATA)/Broken_Links/email/@Value(date_email)
    DATASET_ATTR = _dataset
    FEATURE_TYPE_LIST_ATTR = _feature_type
    FORMAT = CSV2
    TOTAL_FEATURES_WRITTEN_ATTR = _total_features_written
    SUMMARY -> FeatureMerger [SUPPLIER]

Bookmark: Mise à jour de la date d'envoi du courriel dans la BD
ListExploder
    ATTR_ACCUM_MODE = Merge List Attributes
    ATTR_CONFLICT_RES = Use List Attribute Values
    INDEX_ATTR = _element_index
    LIST_ATTR = _list_Par_courriel{}
    ELEMENTS -> AttributeKeeper
AttributeKeeper
    KEEP_ATTRS = date_email,url,broken_link_status_date,metadata_uuid,broken_link_status
    -> DateTimeConverter_2
DateTimeConverter_2
    DATETIME_ATTR = date_email
    OUT_FORMAT = %Y-%m-%d
    PASSTHROUGH = NO
    REPAIR_INPUT = YES
    -> SQLExecutor [INITIATOR]
SQLExecutor
    COMBINE_ATTRS = Result Attributes Only
    COMBINE_GEOM = Initiator Geometry Only
    DATASET = FGP_data_AWS
    FORMAT = POSTGRES
    POSTGRES_CREATE_FEATURE_TABLES_FROM_DATA = Yes
    POSTGRES_NAMED_CONNECTION = FGP_data_AWS
    POSTGRES_QUERY_FEATURE_TYPES_FOR_MERGE_FILTERS = Yes
    POSTGRES_READ_TIME_WITH_TIMEZONE = Yes
    POSTGRES_SCHEMAS_FOR_TABLE_LISTING = broken_links.broken_links_issues
    SQL_STATEMENT:
      UPDATE broken_links.broken_links_issues
      SET date_email = '@Value(date_email)'
      WHERE metadata_uuid = '@Value(metadata_uuid)' AND url = '@Value(url)' AND broken_link_status_date = '@Value(broken_link_status_date)' AND broken_link_status = 'CONFIRMED'
    INITIATOR -> SQLExecutor_2 [INITIATOR]

Bookmark: Validation du bon fonctionnement du Update BD
SQLExecutor_2
    COMBINE_ATTRS = Keep Initiator Attributes if Conflict
    COMBINE_GEOM = Initiator Geometry Only
    DATASET = FGP_data_AWS
    EXPOSED_ATTRIBUTE_LIST = validation
    FORMAT = POSTGRES
    POSTGRES_CREATE_FEATURE_TABLES_FROM_DATA = Yes
    POSTGRES_NAMED_CONNECTION = FGP_data_AWS
    POSTGRES_QUERY_FEATURE_TYPES_FOR_MERGE_FILTERS = Yes
    POSTGRES_READ_TIME_WITH_TIMEZONE = Yes
    POSTGRES_SCHEMAS_FOR_TABLE_LISTING = broken_links.broken_links_issues
    SQL_STATEMENT = SELECT COUNT(*) AS validation FROM broken_links.broken_links_issues WHERE metadata_uuid = '@Value(metadata_uuid)' AND url = '@Value(url)' AND broken_link_status_date = '@Value(broken_link_status_date)' AND broken_link_status = 'CONFIRMED' AND date_email = '@Value(date_email)'
    RESULT -> Tester
Tester
    BOOL_OP = OR
    COMPOSITE_TEST = 1
    TEST_CLAUSE = TEST @Value(validation) != 1
    TEST_MODE = TEST
    PASSED -> Terminator
Terminator
    MESSAGE:
      Problème au niveau du Update du champs date_email dans la table broken_links_issues
      -Présence de doublons update non unique
      -Aucun update de fait (problème correspondance avec éléments présents dans Table)

FME custom transformer Catalogue Reader
Transformer permettant d'obtenir les enregistrements présents dans les catalogues staging et prod (internes et externes).
Il est possible de faire un tri des jeux de données par provinces ou de spécifier un identifiant unique ou une liste d'identifiant à rechercher.

Parameters:
- LOOKUP_LISTBOX =
- SOURCE_URL =
- CUSTOM_URL =
- CKAN_FILTER = fq=collection:fgp   # fq=collection:fgp CKAN_FILTER
- CUSTOM_CSW_SCHEMA =
- CUSTOM_CSW_VERSION =
- CUSTOM_URL_CSW_TYPENAMES =
- CUSTOM_CSW_LIST_NAME = DefaultNoList{}
- IDENTIFIANT =
- CUSTOM_URL_BY_ID_ATT_NAME =
- CSW_ANYTEXT_FILTER =

AttributeFilter
    ATTR_NAME = _type_requete
    ATTR_VALUES = CKAN-AllRecords,CSW-AllRecords,CKAN-ByID,CSW-ByID,<Empty>,<Missing>,<Null>,<Unfiltered>
    CKAN-AllRecords -> Tester_2
    CSW-AllRecords -> Tester_13
    CKAN-ByID -> HTTPCaller_4
    CSW-ByID -> HTTPCaller_2
    <EMPTY> -> Terminator_5
    <MISSING> -> Terminator_5
    <NULL> -> Terminator_5
    <UNFILTERED> -> Terminator_5
Terminator_10
    MESSAGE = Translation Terminated
BulkAttributeRenamer
    ATTRCHOICE = All Attributes
    CASE_DISP = NO
    MODE_CHOICE = RENAME
    PATTERN_ACTION_DISP = STRINGREPLACE
    REPLACE_PATTERN = temp_name_
    REPLACE_STR = @Value(_list_name)
    -> AttributeExploder
Terminator_5
    MESSAGE = Translation Terminated
AttributeRemover
    REMOVE_ATTRS = _response_body,root_url,_http_status_code,ErreurUUID,_id,_type_requete
    -> Résultats (output)
Résultats (output)
Identifiant_Non_trouvé: AttributeCreator
    ATTR_TABLE = SET_TO Statut = Métadonnée non trouvée
    -> AttributeRemover_2
AttributeRemover_2
    LIST_ATTRS = MD_Metadata{}
    REMOVE_ATTRS = _id,_http_status_code,fme_rejection_code,ErreurUUID,Statut
    -> Logger_2
Logger_2
    LOG_FEATURE = LOG_ONLY
    MAXCOORDS = 20
    MAXFEATS = 1000
    MESSAGE = Problème au niveau de la liste d'Identifiants (UUID invalide, présence d'espace, etc)  ou Problème d'accessibilité de l'Environnement sélectionné (serveur Down, UUID non présent dans l'environnement choisi)
    SEVERITY = WARN
    LOGGED -> MetadonnéesNonTrouvées (output)
MetadonnéesNonTrouvées (output)

Bookmark: Préparation du call HTTP
Input (input)
    -> AttributeCreator_2
Note: Transfert des paramètres en attributs
AttributeCreator_2
    ATTR_TABLE:
      SET_TO _id = $(IDENTIFIANT)
      SET_TO root_url = $(SOURCE_URL)
    -> Tester_8
Note: CUSTOM URL
Tester_8
    BOOL_OP = OR
    COMPOSITE_TEST = 1
    TEST_CLAUSE = TEST $(CUSTOM_URL) != ""
    TEST_MODE = TEST
    PASSED -> AttributeCreator_8
    FAILED -> Tester_7
Note: On écrase la valeur
AttributeCreator_8
    ATTR_TABLE = SET_TO root_url = $(CUSTOM_URL)
    -> Tester_7
Note: CKAN ou CSW
Tester_7
    BOOL_OP = OR
    COMPOSITE_TEST = 1
    TEST_CLAUSE = CASE_INSENSITIVE_TEST @LowerCase(@Value(root_url)) CONTAINS csw
    TEST_MODE = CASE_INSENSITIVE_TEST
    PASSED -> AttributeCreator_9
    FAILED -> AttributeCreator_10
AttributeCreator_9
    ATTR_TABLE = SET_TO _type_requete = CSW
    -> Tester_3
AttributeCreator_10
    ATTR_TABLE = SET_TO _type_requete = CKAN
    -> Tester_3
Note: All records / By record
Tester_3
    BOOL_OP = OR
    COMPOSITE_TEST = 1
    TEST_CLAUSE = TEST _id NOT_ATTRIBUTE_HAS_A_VALUE ""
    TEST_MODE = TEST
    PASSED -> AttributeCreator_12
    FAILED -> Logger
Logger
    LOG_FEATURE = LOG_ONLY
    MAXCOORDS = 20
    MAXFEATS = 20
    MESSAGE = La présence d'un attribut "Identifiant" bypass le tri par attribut "provider".
    SEVERITY = WARN
    LOGGED -> PythonCaller
AttributeCreator_11
    ATTR_TABLE = SET_TO _type_requete = @Value(_type_requete)-ByID
    -> Tester
UUID_invalide (output)
AttributeCreator_12
    ATTR_TABLE = SET_TO _type_requete = @Value(_type_requete)-AllRecords
    -> Tester

Bookmark: Validation UUID
PythonCaller
    NEW_ATTRIBUTES = ErreurUUID
    PYTHONSOURCE:
      import fme
      import fmeobjects
      from uuid import UUID
      # Template Function interface:
      # When using this function, make sure its name is set as the value of
      # the 'Class or Function to Process Features' transformer parameter
      def processFeature(feature):
          if not validate_uuid4(feature.getAttribute('_id')):
              feature.setAttribute("ErreurUUID","OUI")

      def validate_uuid4(uuid):

          """
          Validate that a UUID string is in
          fact a valid uuid4.
          Happily, the uuid module does the actual
          checking for us.
          It is vital that the 'version' kwarg be passed
          to the UUID() call, otherwise any 32-character
          hex string is considered valid.
          """

          try:
              val = UUID(uuid, version=4)
              return True
          except ValueError:

              return False
    PYTHONSYMBOL = processFeature
    -> Tester_4
Tester_4
    BOOL_OP = OR
    COMPOSITE_TEST = 1
    TEST_CLAUSE = TEST @Value(ErreurUUID) = OUI
    TEST_MODE = TEST
    PASSED -> UUID_invalide (output)
    FAILED -> AttributeCreator_11

Bookmark: CUSTOM CSW or FGP stuff
Tester
    BOOL_OP = OR
    COMPOSITE_TEST = 1
    TEST_CLAUSE = CASE_INSENSITIVE_TEST @LowerCase(@Value(root_url)) CONTAINS csw
    TEST_MODE = CASE_INSENSITIVE_TEST
    PASSED -> Tester_5
    FAILED -> AttributeFilter
Note: Custom URL Defined
Tester_5
    BOOL_OP = OR
    COMPOSITE_TEST = 1
    TEST_CLAUSE = TEST $(CUSTOM_URL) != ""
    TEST_MODE = TEST
    PASSED -> Tester_9
    FAILED -> AttributeCreator_5
Tester_9
    BOOL_OP = COMPOSITE
    COMPOSITE_TEST = 1 AND 2
    TEST_CLAUSE:
      TEST $(CUSTOM_CSW_VERSION) != ""
      TEST $(CUSTOM_CSW_SCHEMA) != ""
    TEST_MODE = TEST
    PASSED -> AttributeCreator_13
    FAILED -> Terminator_9
AttributeCreator_13
    ATTR_TABLE:
      SET_TO csw_version = $(CUSTOM_CSW_VERSION)
      SET_TO csw_schema = $(CUSTOM_CSW_SCHEMA)
    -> Tester_12
Tester_12
    BOOL_OP = OR
    COMPOSITE_TEST = 1
    TEST_CLAUSE = TEST $(CUSTOM_URL_CSW_TYPENAMES) != ""
    TEST_MODE = TEST
    PASSED -> AttributeCreator_15
    FAILED -> AttributeFilter
AttributeCreator_15
    ATTR_TABLE = SET_TO csw_typenames = &typeNames=$(CUSTOM_URL_CSW_TYPENAMES)
    -> AttributeFilter
Terminator_9
    MESSAGE = Translation Terminated
AttributeCreator_5
    ATTR_TABLE:
      SET_TO csw_version = 2.0.2
      SET_TO csw_schema = http://www.isotc211.org/2005/gmd
      SET_TO csw_typenames = &typeNames=gmd:MD_Metadata
      SET_TO csw_filter = &constraintLanguage=FILTER
    -> AttributeFilter

Bookmark: Adding filter for OPenMaps
Note: OPenMaps ou autreCKAN
Tester_2
    BOOL_OP = OR
    COMPOSITE_TEST = 1
    TEST_CLAUSE = TEST $(CKAN_FILTER) != ""
    TEST_MODE = TEST
    PASSED -> AttributeCreator_4
    FAILED -> HTTPCaller_5
AttributeCreator_4
    ATTR_TABLE = SET_TO _OpenMapsFilter = &$(CKAN_FILTER)
    -> HTTPCaller_5

Bookmark: Lecture CKAN_OpenMaps
Note: Obtenir le nombre feature dans CKAN dans la collection FGP
HTTPCaller_5
    CONNECTION_TIMEOUT_LENGTH = 60
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = @Value(root_url)/package_search?start=0&rows=1@Value(_OpenMapsFilter)
    TRANSFER_TIMEOUT_LENGTH = 90
    USE_COOKIES = No
    VERIFY_SSL_CERTIFICATES = No
    -> JSONFlattener_2
    <REJECTED> -> Terminator_6
JSONFlattener_2
    ERROR_LIST_ATTR = _json_error
    JSON_DOCUMENT = @Value(_response_body)
    READ_FROM_FILE = NO
    RECURSIVE = Yes
    -> AttributeExposer_3
    <REJECTED> -> Terminator_7
AttributeExposer_3
    ATTR_LIST = result.count
    -> AttributeCreator_6
AttributeCreator_6
    ATTR_TABLE = SET_TO nb_paquet = @Evaluate(@ceil(@Value(result.count)/10))
    -> Cloner_2
Cloner_2
    COPIES = @Value(nb_paquet)
    COPYATT = _copynum
    COPY -> AttributeCreator_7
AttributeCreator_7
    ATTR_TABLE = SET_TO start_index = @Evaluate(@Value(_copynum)*10)
    -> AttributeKeeper_2
AttributeKeeper_2
    KEEP_ATTRS = _OpenMapsFilter,start_index,root_url
    -> HTTPCaller_7
Note: Lecture CKAN
HTTPCaller_7
    CONNECTION_TIMEOUT_LENGTH = 60
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = @Value(root_url)/package_search?start=@Value(start_index)&rows=10@Value(_OpenMapsFilter)
    TRANSFER_TIMEOUT_LENGTH = 90
    USE_COOKIES = No
    VERIFY_SSL_CERTIFICATES = No
    -> JSONFlattener_3
    <REJECTED> -> Terminator_8
JSONFlattener_3
    ERROR_LIST_ATTR = _json_error
    JSON_DOCUMENT = @Value(_response_body)
    READ_FROM_FILE = NO
    RECURSIVE = Yes
    -> AttributeExposer_4
AttributeExposer_4
    ATTR_LIST = result.results{}
    -> ListExploder_4
ListExploder_4
    ATTR_ACCUM_MODE = Merge List Attributes
    ATTR_CONFLICT_RES = Use List Attribute Values
    INDEX_ATTR = _element_index
    LIST_ATTR = result.results{}
    ELEMENTS -> AttributeExploder
    <REJECTED> -> Terminator_10
Terminator_8
    MESSAGE = Translation Terminated
Terminator_7
    MESSAGE = Translation Terminated
Terminator_6
    MESSAGE = Translation Terminated

Bookmark: Gestion du nombre d'entités à traiter pour le bon fonctionnement du processus. lot de 10 entrées à la fois.
Tester_13
    BOOL_OP = OR
    COMPOSITE_TEST = 1
    TEST_CLAUSE = TEST $(CSW_ANYTEXT_FILTER) = ""
    TEST_MODE = TEST
    PASSED -> HTTPCaller
    FAILED -> AttributeCreator_17
AttributeCreator_17
    ATTR_TABLE = SET_TO _temp_csw_search_criteria = $(CSW_ANYTEXT_FILTER)
    -> TextEncoder
TextEncoder
    DEST_ATTR = _temp_csw_search_criteria
    ENCODING_TYPE = URL_ENCODE
    STRING_TO_ENCODE = @Value(_temp_csw_search_criteria)
    -> AttributeCreator_16
AttributeCreator_16
    ATTR_TABLE = SET_TO csw_search_criteria = &constraintlanguage=CQL_TEXT&constraint=apiso%3AAnyText%20like%20@Value(_temp_csw_search_criteria)
    -> HTTPCaller
Note: Identifier le nombre de fichiers dans le noeud CSW
HTTPCaller
    CONNECTION_TIMEOUT_LENGTH = 60
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = @Value(root_url)request=GetRecords&service=CSW&version=@Value(csw_version)&elementSetName=full@Value(csw_typenames)@Value(csw_filter)@Value(csw_search_criteria)
    TRANSFER_TIMEOUT_LENGTH = 90
    USE_COOKIES = No
    VERIFY_SSL_CERTIFICATES = No
    -> XMLFlattener_2
    <REJECTED> -> Terminator_3
Note: Extraire l'information
XMLFlattener_2
    ATTRIBUTE_XML = _response_body
    EMBEDDED_EXPRESSIONS = SearchResults
    FEATURE_TYPES_FORMAT_NAME = XML
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    NEW_ATTRIBUTES = SearchResults.numberOfRecordsMatched
    XML_SOURCE_TYPE = Attribute with XML document
    -> AttributeCreator
    <REJECTED> -> Terminator
Note: Calculer le nombre de paquets pour la lecture
AttributeCreator
    ATTR_TABLE:
      SET_TO NbPaquets = @Evaluate(@ceil(@Value(SearchResults.numberOfRecordsMatched)/10))
      SET_TO NbRecords = @Value(SearchResults.numberOfRecordsMatched)
    -> Cloner
Cloner
    COPIES = @Value(NbPaquets)
    COPYATT = _copynum
    COPY -> AttributeCreator_22
AttributeCreator_22
    ATTR_TABLE = SET_TO debut = @Evaluate(1+@Value(_copynum)*10)
    -> AttributeKeeper
AttributeKeeper
    KEEP_ATTRS = csw_schema,csw_search_criteria,csw_version,root_url,NbRecords,debut,csw_filter,csw_typenames
    -> HTTPCaller_3
Note: Lecutre par paquet de 10
HTTPCaller_3
    CONNECTION_TIMEOUT_LENGTH = 60
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = @Value(root_url)request=GetRecords&service=CSW&version=@Value(csw_version)&elementSetName=full&ElementSetName=full&resultType=results&startPosition=@Value(debut)&maxRecords=10&outputSchema=@Value(csw_schema)@Value(csw_filter)@Value(csw_typenames)@Value(csw_search_criteria)
    TRANSFER_TIMEOUT_LENGTH = 90
    USE_COOKIES = No
    VERIFY_SSL_CERTIFICATES = No
    -> XMLFlattener
    <REJECTED> -> Terminator_4
XMLFlattener
    ATTRIBUTE_XML = _response_body
    EMBEDDED_EXPRESSIONS = SearchResults
    FEATURE_TYPES_FORMAT_NAME = XML
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    XML_SOURCE_TYPE = Attribute with XML document
    -> Tester_10
Note: Custom URL Defined
Tester_10
    BOOL_OP = OR
    COMPOSITE_TEST = 1
    TEST_CLAUSE = TEST $(CUSTOM_URL) != ""
    TEST_MODE = TEST
    PASSED -> ListExploder_3
    FAILED -> AttributeExposer
Note: Créer une entité par métadonnées
ListExploder_3
    ATTR_ACCUM_MODE = Prefix List Attributes
    INCOMING_PREFIX = temp_name_.
    INDEX_ATTR = _element_index
    LIST_ATTR = $(CUSTOM_CSW_LIST_NAME)
    ELEMENTS -> AttributeCreator_14
AttributeCreator_14
    ATTR_TABLE = SET_TO _list_name = $(CUSTOM_CSW_LIST_NAME)
    -> StringReplacer
StringReplacer
    CASE = NO
    FIND_TEXT = {}
    NO_MATCH = _FME_NO_OP_
    REGEXP = NO
    SRC_ATTRS = _list_name
    -> BulkAttributeRenamer
AttributeExposer
    ATTR_LIST = MD_Metadata{}
    -> ListExploder_2
Note: Créer une entité par métadonnées
ListExploder_2
    ATTR_ACCUM_MODE = Prefix List Attributes
    INCOMING_PREFIX = MD_Metadata.
    INDEX_ATTR = _element_index
    LIST_ATTR = MD_Metadata{}
    ELEMENTS -> AttributeExploder
    <REJECTED> -> AttributeExploder
Terminator_4
    MESSAGE = Translation Terminated
Terminator
    MESSAGE = Translation Terminated
Terminator_3
    MESSAGE = Translation Terminated

Bookmark: Extraction des données selon la licence. Le modèle de données n'importe pas
AttributeExploder
    ATTR_NAME_LABEL = _attr_name
    ATTR_VALUE_LABEL = _attr_value
    EXPLODING_TYPE = List
    KEEP_ATTRIBUTES = Yes
    KEEP_GEOMETRY = No
    LIST_NAME = _attr_list
    -> AttributeCreator_3
Note: Transfert en attributs des provider à identifier
AttributeCreator_3
    ATTR_TABLE = SET_TO list_provider = $(FILTER_PROVIDER)
    -> AttributeTrimmer
AttributeTrimmer
    SRC_ATTRS = list_provider
    TRIM_CHARS = "
    TRIM_TO_NONE = Yes
    TRIM_TYPE = Both
    -> AttributeSplitter
AttributeSplitter
    ATTR_NAME = list_provider
    DELIMITER = " "
    DROP_EMPTY_PARTS = No
    LIST_NAME = _listprovider
    TRIM_OPTION = Both
    -> ListConcatenator
ListConcatenator
    DROP_EMPTY_PARTS = No
    LIST_ATTR = _attr_list{}._attr_value
    SEP = ,
    VAL_ATTR = _concatenated
    -> AttributeRemover_4
AttributeRemover_4
    LIST_ATTRS = _attr_list{} _attr_list{}._attr_name _attr_list{}._attr_value
    -> PythonCaller_2
Note: Recherche dans la liste de valeur, les licences attendues
PythonCaller_2
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass
          def input(self,feature):
              list_provider=feature.getAttribute('_listprovider{}')
              list_text=feature.getAttribute('_concatenated')

              for provider in list_provider:
                  if provider in list_text:
                      self.pyoutput(feature)
                      break

          def close(self):
              pass
    PYTHONSYMBOL = FeatureProcessor
    -> AttributeRemover_3
AttributeRemover_3
    LIST_ATTRS = _listprovider{}
    REMOVE_ATTRS = debut,NbRecords,_response_body,list_provider,_concatenated,fme_rejection_code,root_url,_http_status_code,start_index,_element_index
    -> BulkAttributeRemover
BulkAttributeRemover
    ATTR_EXP = SearchResults^
    -> Résultats (output)

Bookmark: Lecture dans CKAN par ID
Note: CKAN
HTTPCaller_4
    CONNECTION_TIMEOUT_LENGTH = 60
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = @Value(root_url)/package_show?id=@Value(_id)
    TRANSFER_TIMEOUT_LENGTH = 90
    USE_COOKIES = No
    VERIFY_SSL_CERTIFICATES = No
    -> JSONFlattener
    <REJECTED> -> Identifiant_Non_trouvé
JSONFlattener
    ERROR_LIST_ATTR = _json_error
    JSON_DOCUMENT = @Value(_response_body)
    READ_FROM_FILE = NO
    RECURSIVE = Yes
    -> AttributeExposer_2
    <REJECTED> -> Identifiant_Non_trouvé
AttributeExposer_2
    ATTR_LIST = result.file_id
    -> AttributeRemover

Bookmark: Requête CSW - GetRecordByID
Note: CSW
HTTPCaller_2
    CONNECTION_TIMEOUT_LENGTH = 60
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = @Value(root_url)request=GetRecordById&service=CSW&version=@Value(csw_version)&elementSetName=full&id=@Value(_id)&outputSchema=@Value(csw_schema)@Value(csw_typenames)@Value(csw_filter)
    TRANSFER_TIMEOUT_LENGTH = 90
    USE_COOKIES = No
    VERIFY_SSL_CERTIFICATES = No
    -> Tester_6
    <REJECTED> -> Logger_2
Note: Custom URL Defined
Tester_6
    BOOL_OP = OR
    COMPOSITE_TEST = 1
    TEST_CLAUSE = TEST $(CUSTOM_URL) != ""
    TEST_MODE = TEST
    PASSED -> Tester_11
    FAILED -> XMLFlattener_3
Tester_11
    BOOL_OP = OR
    COMPOSITE_TEST = 1
    TEST_CLAUSE = TEST $(CUSTOM_URL_BY_ID_ATT_NAME) != ""
    TEST_MODE = TEST
    PASSED -> XMLFlattener_4
    FAILED -> Terminator_2
XMLFlattener_4
    ATTRIBUTE_XML = _response_body
    EMBEDDED_EXPRESSIONS = $(CUSTOM_URL_BY_ID_ATT_NAME)
    FEATURE_TYPES_FORMAT_NAME = XML
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    XML_SOURCE_TYPE = Attribute with XML document
    -> AttributeRemover
    <REJECTED> -> Identifiant_Non_trouvé
Terminator_2
    MESSAGE = Translation Terminated
XMLFlattener_3
    ATTRIBUTE_XML = _response_body
    EMBEDDED_EXPRESSIONS = GetRecordByIdResponse
    FEATURE_TYPES_FORMAT_NAME = XML
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    XML_SOURCE_TYPE = Attribute with XML document
    -> AttributeRemover
    <REJECTED> -> Identifiant_Non_trouvé

FME custom transformer FMEServerEmailGenerator
Description
This transformer provides an easy method for creating an email message to be sent by the FME Server Notification Service.
Input Ports
Input
This transformer will accept any feature.
Output Ports
Output
Features are output with text_line_data attribute required for the Text File Writer (see Usage Notes).
text_line_data: Contains JSON-formatted message that is required by the Email Subscription (see Usage Notes).
<Rejected>
Features will be rejected if the 'To:' field does not contain a valid email address in the form email@domain. Rejected features are output with value INVALID_PARAMETER stored in the fme_rejection_code attribute.
Parameters
To
Email address for To: field. 
Cc
Email address for Cc: field.
Bcc
Email address for Bcc: field.
From
Email address for From: field.
Reply to
Email address for Reply to: field.
Subject
Text string for subject of email.
Content
The main body of the email message.
Attachments
List of files to attach to email. For multiple files, separate filenames with a comma (e.g. file1.txt,file2.txt). File paths and features stored as attributes are both accepted.
Note: Attachments may not process if not accessible by FME Server.  
Usage Notes
Step 1. Create Topic and Email Subscription
In the FME Server Web UI, create a Topic for notifications to be sent to, and also create an Email Subscription that subscribes to this Topic.
Step 2. Create a Workspace
Once you fill out the the required paramerts for this transformer, you can send the email message in two different ways:
A. Send an email when the workspace completes:  
Add a Text File Writer to the workspace  
Connect FMEServerEmailGenerator Output to the Text File Writer  
Publish the workspace to FME Server
Register it with the Job Submitter, and/or Data Download, and/or Notification Service  
For each service, click the edit button  
Expand the Notify on Job Completion section
For Topics to Publish (Success), select the Topic created in Step 1  
For the Post Data parameter, select the Text File Writer added to the workspace  
Finish publishing the workspace  
Now the workspace will send an email whenever it is run through the FME Server Service you registered it with  
B. Send an email using a transformer:  
Add an FMEServerNotifier transformer to your workflow  
Configure it to publish to the Topic that you created earlier  
For Content, select the text_line_data attribute  
Now the workspace will send an email whenever it is run

Parameters:
- email_to =   # To
- email_cc =   # Cc
- email_bcc =   # Bcc
- email_from =   # From
- email_replyto =   # Reply to
- email_subject =   # Subject
- email_subscriber_content =   # Content
- email_attachment_paths =   # Attachments

Input (input)
    -> Counter
Tester_2_FAILED: Junction
    -> AttributeCreator_3
Note: Rejected
AttributeCreator_3: Junction
    -> AttributeCreator_2
AttributeCreator_2
    ATTR_TABLE = SET_TO fme_rejection_code = INVALID_PARAMETER
    -> <Rejected> (output)
<Rejected> (output)
JSONTemplater_2_ROOT: Junction
    -> JSONTemplater_2 [ROOT]
Note: No attachment
Output_2: Junction
    -> Output (output)
Output (output)

Bookmark: Parse for attachement
Counter
    CNT_ATTR = _email_feature_id
    DOMAIN = counter
    SCOPE = Local
    START = 0
    -> ParameterFetcher
ParameterFetcher
    ATTR_LIST = _email_from $(email_from) _email_replyto $(email_replyto) _email_attachment_paths $(email_attachment_paths) _email_cc $(email_cc) _email_bcc $(email_bcc)
    -> AttributeCreator
AttributeCreator
    ATTR_TABLE:
      SET_TO _email_to = $(email_to)
      SET_TO _email_subject = $(email_subject)
      SET_TO _email_subscriber_content = $(email_subscriber_content)
    -> Tester_2
Note: Test that To field contains / valid email address
Note: Reject
Tester_2
    BOOL_OP = OR
    COMPOSITE_TEST = 1
    TEST_CLAUSE = TEST @Value(_email_to) CONTAINS @
    TEST_MODE = TEST
    PASSED -> Tester_3
    FAILED -> Tester_2_FAILED

Bookmark: Multiple attachment string wizardy
Tester_3
    BOOL_OP = OR
    COMPOSITE_TEST = 1
    TEST_CLAUSE = TEST @Value(_email_attachment_paths) CONTAINS " "
    TEST_MODE = TEST
    PASSED -> SubstringExtractor
    FAILED -> Tester_3_FAILED
SubstringExtractor
    END = -2
    RESULT_ATTR = _email_attachment_paths
    SRC_STRING = @Value(_email_attachment_paths)
    START = 1
    -> StringReplacer_3
StringReplacer_3
    CASE = NO
    FIND_TEXT = " "
    NO_MATCH = _FME_NO_OP_
    REGEXP = NO
    REPLACE_TEXT = "" ""
    SRC_ATTRS = _email_attachment_paths
    -> JSONTemplater [ROOT]
Note: Single attachment
Tester_3_FAILED: Junction
    -> JSONTemplater_2_ROOT

Bookmark: Add multiple attachments
JSONTemplater
    RESULT_ATTRIBUTE = text_line_data
    ROOT_QUERY_EXPR:
      {
      "email_to": fme:get-attribute("_email_to"),
      "email_cc": fme:get-attribute("_email_cc"),
      "email_bcc": fme:get-attribute("_email_bcc"),
      "email_from": fme:get-attribute("_email_from"),
      "email_replyto": fme:get-attribute("_email_replyto"),
      "email_subject": string(fme:get-attribute("_email_subject")),
      "subscriber_content": string(fme:get-attribute("_email_subscriber_content"))
      }
    VISIBLE_QUERY_VALIDATE = Yes
    -> Tester
Tester
    BOOL_OP = OR
    COMPOSITE_TEST = 1
    TEST_CLAUSE = TEST _email_attachment_paths ATTRIBUTE_IS_EMPTY ""
    TEST_MODE = TEST
    PASSED -> Tester_PASSED
    FAILED -> AttributeSplitter_2
AttributeSplitter_2
    ATTR_NAME = _email_attachment_paths
    DELIMITER = " "
    DROP_EMPTY_PARTS = No
    LIST_NAME = _email_attachment_path_list
    TRIM_OPTION = Both
    -> ListExploder_2
ListExploder_2
    ATTR_ACCUM_MODE = Merge List Attributes
    ATTR_CONFLICT_RES = Use List Attribute Values
    INDEX_ATTR = _element_index
    LIST_ATTR = _email_attachment_path_list{}
    ELEMENTS -> StringConcatenator_2
StringConcatenator_2
    ACTION = Create New Attribute
    PARM_LINE = "email_attachment{@Value(_element_index)}":@Value(_email_attachment_path_list)
    VAL_ATTR = _email_attachment_json
    -> Aggregator_2
Aggregator_2
    ACCUM_ATTRS_NAME = Merge Incoming Attributes
    AGGREGATE_TYPE = Homogeneous Collection (If Possible)
    CONCAT_ATTRS = _email_attachment_json
    GROUP_BY = _email_feature_id
    MODE = Geometry - Assemble One Level
    SEP = ,
    AGGREGATE -> StringReplacer_5
StringReplacer_5
    CASE = NO
    FIND_TEXT = \
    NO_MATCH = _FME_NO_OP_
    REGEXP = NO
    REPLACE_TEXT = \\
    SRC_ATTRS = _email_attachment_json
    -> StringReplacer_4
StringReplacer_4
    CASE = NO
    FIND_TEXT = }
    NO_MATCH = _FME_NO_OP_
    REGEXP = NO
    REPLACE_TEXT = , @Value(_email_attachment_json)}
    SRC_ATTRS = text_line_data
    -> Output (output)
Note: No attachment
Tester_PASSED: Junction
    -> Output_2

Bookmark: Add single attachment
JSONTemplater_2
    RESULT_ATTRIBUTE = text_line_data
    ROOT_QUERY_EXPR:
      {
      "email_to": fme:get-attribute("_email_to"),
      "email_cc": fme:get-attribute("_email_cc"),
      "email_bcc": fme:get-attribute("_email_bcc"),
      "email_from": fme:get-attribute("_email_from"),
      "email_replyto": fme:get-attribute("_email_replyto"),
      "email_subject": string(fme:get-attribute("_email_subject")),
      "subscriber_content": string(fme:get-attribute("_email_subscriber_content"))
      }
    VISIBLE_QUERY_VALIDATE = Yes
    -> Tester_4
Tester_4
    BOOL_OP = OR
    COMPOSITE_TEST = 1
    TEST_CLAUSE = TEST _email_attachment_paths ATTRIBUTE_IS_EMPTY ""
    TEST_MODE = TEST
    PASSED -> Tester_PASSED_2
    FAILED -> AttributeSplitter
AttributeSplitter
    ATTR_NAME = _email_attachment_paths
    DELIMITER = " "
    DROP_EMPTY_PARTS = No
    LIST_NAME = _email_attachment_path_list
    TRIM_OPTION = Both
    -> ListExploder
ListExploder
    ATTR_ACCUM_MODE = Merge List Attributes
    ATTR_CONFLICT_RES = Use List Attribute Values
    INDEX_ATTR = _element_index
    LIST_ATTR = _email_attachment_path_list{}
    ELEMENTS -> StringConcatenator
StringConcatenator
    ACTION = Create New Attribute
    PARM_LINE = "email_attachment{@Value(_element_index)}":"@Value(_email_attachment_path_list)"
    VAL_ATTR = _email_attachment_json
    -> Aggregator
Aggregator
    ACCUM_ATTRS_NAME = Merge Incoming Attributes
    AGGREGATE_TYPE = Homogeneous Collection (If Possible)
    CONCAT_ATTRS = _email_attachment_json
    GROUP_BY = _email_feature_id
    MODE = Geometry - Assemble One Level
    SEP = ,
    AGGREGATE -> StringReplacer_2
StringReplacer_2
    CASE = NO
    FIND_TEXT = \
    NO_MATCH = _FME_NO_OP_
    REGEXP = NO
    REPLACE_TEXT = \\
    SRC_ATTRS = _email_attachment_json
    -> StringReplacer
StringReplacer
    CASE = NO
    FIND_TEXT = }
    NO_MATCH = _FME_NO_OP_
    REGEXP = NO
    REPLACE_TEXT = , @Value(_email_attachment_json)}
    SRC_ATTRS = text_line_data
    -> Output (output)
Note: No attachment
Tester_PASSED_2: Junction
    -> Output_2
