FME workspace Detection_BrokenLinks.fmw

Parameters:
- IN_CHOICE_JURIDICTION = Tout
- IN_OUT_POSTGRES_CONNECTION = FGP_data_AWS
- OUT_XLS_ERREUR_FORMAT = $(FME_SHAREDRESOURCE_DATA)/Broken_Links/erreur_format.xlsx
- LOG_FILE = $(FME_SHAREDRESOURCE_DATA)/Broken_Links/detection.log   # Log File
- Env_Catalogue = https://maps.canada.ca/geonetwork/srv/eng/csw?

Readers:
- POSTGRES_1: POSTGRES from $(IN_OUT_POSTGRES_CONNECTION)

Writers:
- XLSXW_1: XLSXW to $(OUT_XLS_ERREUR_FORMAT)
- POSTGRES_2: POSTGRES to $(IN_OUT_POSTGRES_CONNECTION)

Creator_6
    GEOMTYPE = Geometry Object
    NUM = 1
    CREATED -> Catalogue_Reader_6
Catalogue_Reader_6: Catalogue Reader
    CKAN_FILTER = fq=collection:fgp
    CUSTOM_CSW_LIST_NAME = DefaultNoList{}
    SOURCE_URL = $(Env_Catalogue)
    UUID_invalide -> Terminator
    Résultats -> AttributeExposer
    MetadonnéesNonTrouvées -> Terminator
Note: _juridiction = IN_CHOICE_JURIDICTION / Il faut re-créer une variable pour le paramètre IN_CHOICE_JURIDICTION car le custom BrokenLinks_Detector ne le retourne pas
AttributeCreator_4
    ATTR_TABLE = SET_TO _juridiction = $(IN_CHOICE_JURIDICTION)
    -> Tester_3
Note: Des enregistrements de liens brisés sont créés si / _juridiction = Tout / ou / _juridiction = IN_JURIDICTION i.e. la juridiction qui a été déterminée par BrokenLinks_Detector
Tester_3
    BOOL_OP = OR
    COMPOSITE_TEST = 1 OR 2
    TEST_CLAUSE:
      CASE_INSENSITIVE_TEST @Value(IN_JURIDICTION) = @Value(_juridiction)
      CASE_INSENSITIVE_TEST @Value(_juridiction) = Tout
    TEST_MODE = CASE_INSENSITIVE_TEST
    PASSED -> FeatureHolder
FeatureHolder
    -> BrokenLinks_Detector_python [Input_Metadata_2]
BrokenLinks_Detector_python
    Broken_Links -> PeuplerBrokenLinks_v10 [IN_ERREUR]
    Broken_Links -> PeuplerBrokenLinks_FIXED_v3 [IN_ERREUR]
Terminator
    MESSAGE = UUID invalide ou non trouvé dans l'environnement sélectionné
cl_resource_format (reader POSTGRES_1)
    attributes: format varchar(80),PrimaryKey, description_en varchar(80), description_fr varchar(80)
    -> PeuplerBrokenLinks_v10 [IN_RESOURCE_FORMAT]
cl_broken_link_problem (reader POSTGRES_1)
    attributes: problem varchar(80),PrimaryKey, description_en varchar(80), description_fr varchar(80)
    -> PeuplerBrokenLinks_v10 [IN_TYPE_ERREUR]
broken_links_issues (reader POSTGRES_1)
    attributes: metadata_uuid uuid,PrimaryKey, url varchar(80), resource_format varchar(80),BTREE, broken_link_problem varchar(80), broken_link_status varchar(80), broken_link_status_date date, juridiction text, date_email date
    -> AttributeCreator_6
    -> PeuplerBrokenLinks_v10 [IN_BROKEN_LINKS_ISSUES]
PeuplerBrokenLinks_v10
    Unknown_Format -> Unknown_Format
    Unknown_Format -> AttributeCreator_3
    OUT_BROKEN_LINKS_ISSUES -> Sorter
    Unknown_Type_Erreur -> Logger
    Unknown_Statut -> Unknown_Statut
Unknown_Format: Logger
    LOG_FEATURE = LOG_ONLY
    MAXCOORDS = 20
    MAXFEATS = 20
    MESSAGE = ERREUR DE FORMAT : @Value(IN_METADATA_UUID), FORMAT : @Value(IN_RESOURCE_FORMAT)
    SEVERITY = INFO
AttributeCreator_3
    ATTR_TABLE = SET_TO broken_link_status_date = @DateTimeNow()
    -> DateTimeConverter_2
DateTimeConverter_2
    DATETIME_ATTR = broken_link_status_date
    OUT_FORMAT = %Y-%m-%d
    PASSTHROUGH = NO
    REPAIR_INPUT = YES
    -> FORMAT INVALIDE (writer XLSXW_1)
FORMAT INVALIDE (writer XLSXW_1)
    attributes: METADATA_UUID string(38), JURIDICTION string(10), RESOURCE_FORMAT string(20), BROKEN_LINK_PROBLEM string(30), BROKEN_LINK_STATUS_DATE date(26), URL string(200)
Logger
    LOG_FEATURE = LOG_ONLY
    MAXCOORDS = 20
    MAXFEATS = 20
    MESSAGE = ERREUR DE TYPE D'ERREUR : @Value(IN_METADATA_UUID), ERREUR : @Value(IN_TYPE_ERREUR)
    SEVERITY = INFO
Unknown_Statut: Logger
    LOG_FEATURE = LOG_ONLY
    MAXCOORDS = 20
    MAXFEATS = 20
    MESSAGE = ERREUR DE STATUT : @Value(IN_METADATA_UUID), STATUT : @Value(_listMerge{0}.broken_link_status)
    SEVERITY = INFO
Note: Pour éviter les conflits d'écriture
Sorter
    SORT_PARM = metadata_uuid ALPHA ASCENDING
    SORTED -> broken_links_issues (writer POSTGRES_2)
Note: _juridiction = IN_CHOICE_JURIDICTION / afin de filter en fonction de la juridiction des liens brisés
AttributeCreator_6
    ATTR_TABLE = SET_TO _juridiction = $(IN_CHOICE_JURIDICTION)
    -> Tester_2
Note: Des enregistrements de liens brisés pourront être mis à FIXED si / _juridiction = Tout / ou / _juridiction = IN_JURIDICTION i.e. la juridiction qui a été déterminée par BrokenLinks_Detector
Tester_2
    BOOL_OP = OR
    COMPOSITE_TEST = 1 OR 2
    TEST_CLAUSE:
      TEST @Value(juridiction) = @Value(_juridiction)
      TEST @Value(_juridiction) = Tout
    TEST_MODE = TEST
    PASSED -> PeuplerBrokenLinks_FIXED_v3 [IN_BROKEN_LINKS_ISSUES]
PeuplerBrokenLinks_FIXED_v3
    BROKEN_LINK_PROBLEM = @Value(broken_link_problem)
    BROKEN_LINK_STATUS = @Value(broken_link_status)
    BROKEN_LINK_STATUS_DATE = @Value(broken_link_status_date)
    IN_JURIDICTION = @Value(IN_JURIDICTION)
    IN_METADATA_UUID = @Value(IN_METADATA_UUID)
    IN_RESOURCE_FORMAT = @Value(IN_RESOURCE_FORMAT)
    IN_TYPE_ERREUR = @Value(IN_TYPE_ERREUR)
    IN_URL_ERRONE = @Value(IN_URL_ERRONE)
    JURIDICTION = @Value(juridiction)
    METADATA_UUID = @Value(metadata_uuid)
    RESOURCE_FORMAT = @Value(resource_format)
    URL = @Value(url)
    OUT_BROKEN_LINKS_ISSUES -> broken_links_issues (writer POSTGRES_2)
broken_links_issues (writer POSTGRES_2)
    attributes: metadata_uuid uuid,PrimaryKey, url varchar(80), resource_format varchar(80),BTree, broken_link_problem varchar(80), broken_link_status varchar(80), broken_link_status_date date, juridiction text

Bookmark: Données Fédérales ou P/T
AttributeExposer
    ATTR_LIST = MD_Metadata.contact.CI_ResponsibleParty.organisationName.CharacterString
    -> Tester
Tester
    BOOL_OP = OR
    COMPOSITE_TEST = 1
    TEST_CLAUSE = CASE_SENSITIVE_TEST @Value(MD_Metadata.contact.CI_ResponsibleParty.organisationName.CharacterString) CONTAINS_REGEX Canada
    TEST_MODE = CASE_SENSITIVE_TEST
    PASSED -> AttributeCreator_17
    FAILED -> AttributeCreator_18
AttributeCreator_17
    ATTR_TABLE = SET_TO IN_JURIDICTION = Fed
    -> AttributeCreator_4
AttributeCreator_18
    ATTR_TABLE = SET_TO IN_JURIDICTION = ProvTer
    -> AttributeCreator_4

Bookmark: Traitement des erreurs
Note: Seules les erreurs de format seront aussi écrites dans la lable broken_links_issues
