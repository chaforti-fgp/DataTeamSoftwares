FME workspace BrokenLinks_DB_Export.fmw

Parameters:
- OUT_XLSX_DIR = $(FME_SHAREDRESOURCE_DATA)\BROKEN_LINKS
- IN_PG_HOST =
- IN_PG_PORT =
- IN_PG_DBNAME =
- IN_PG_USERNAME =
- IN_PG_PWD =

Writers:
- XLSXW_1: XLSXW to $(OUT_XLSX_DIR)

Creator
    GEOMTYPE = Geometry Object
    NUM = 1
    CREATED -> DateTimeStamper
DateTimeStamper
    DATETIME_ATTR = _timestamp
    INCLUDE_OFFSET = NO
    STAMP_TYPE = datetime
    TIMEZONE = local
    -> AttributeSplitter
AttributeSplitter
    ATTR_NAME = _timestamp
    DELIMITER = .
    DROP_EMPTY_PARTS = No
    LIST_NAME = _list
    TRIM_OPTION = Both
    -> AttributeCreator
AttributeCreator
    ATTR_TABLE = SET_TO _date_fichier = @Value(_list{0})
    -> AttributeKeeper
AttributeKeeper
    KEEP_ATTRS = _date_fichier
    -> SQLExecutor [INITIATOR]
    -> SQLExecutor_2 [INITIATOR]
    -> SQLExecutor_3 [INITIATOR]
    -> SQLExecutor_4 [INITIATOR]
SQLExecutor
    COMBINE_ATTRS = Keep Result Attributes if Conflict
    COMBINE_GEOM = Initiator Geometry Only
    DATASET = $(IN_PG_DBNAME)
    EXPOSED_ATTRIBUTE_LIST = format,description_en,description_fr
    FORMAT = POSTGRES
    POSTGRES_CREATE_FEATURE_TABLES_FROM_DATA = Yes
    POSTGRES_HOST = $(IN_PG_HOST)
    POSTGRES_PASSWORD = $(IN_PG_PWD)
    POSTGRES_PORT = $(IN_PG_PORT)
    POSTGRES_QUERY_FEATURE_TYPES_FOR_MERGE_FILTERS = Yes
    POSTGRES_READ_TIME_WITH_TIMEZONE = Yes
    POSTGRES_SSLMODE = prefer
    POSTGRES_USER_NAME = $(IN_PG_USERNAME)
    SQL_STATEMENT = select * from broken_links.cl_resource_format;
    RESULT -> cl_resource_format (writer XLSXW_1)
cl_resource_format (writer XLSXW_1)
    attributes: format auto(20), description_en auto(20), description_fr auto(20)
SQLExecutor_2
    COMBINE_ATTRS = Keep Result Attributes if Conflict
    COMBINE_GEOM = Initiator Geometry Only
    DATASET = $(IN_PG_DBNAME)
    EXPOSED_ATTRIBUTE_LIST = status,description_en,description_fr
    FORMAT = POSTGRES
    POSTGRES_CREATE_FEATURE_TABLES_FROM_DATA = Yes
    POSTGRES_HOST = $(IN_PG_HOST)
    POSTGRES_PASSWORD = $(IN_PG_PWD)
    POSTGRES_PORT = $(IN_PG_PORT)
    POSTGRES_QUERY_FEATURE_TYPES_FOR_MERGE_FILTERS = Yes
    POSTGRES_READ_TIME_WITH_TIMEZONE = Yes
    POSTGRES_SSLMODE = prefer
    POSTGRES_USER_NAME = $(IN_PG_USERNAME)
    SQL_STATEMENT = select * from broken_links.cl_broken_link_status;
    RESULT -> cl_broken_link_status (writer XLSXW_1)
cl_broken_link_status (writer XLSXW_1)
    attributes: status auto(20), description_en auto(20), description_fr auto(20)
SQLExecutor_3
    COMBINE_ATTRS = Keep Result Attributes if Conflict
    COMBINE_GEOM = Initiator Geometry Only
    DATASET = $(IN_PG_DBNAME)
    EXPOSED_ATTRIBUTE_LIST = problem,description_en,description_fr
    FORMAT = POSTGRES
    POSTGRES_CREATE_FEATURE_TABLES_FROM_DATA = Yes
    POSTGRES_HOST = $(IN_PG_HOST)
    POSTGRES_PASSWORD = $(IN_PG_PWD)
    POSTGRES_PORT = $(IN_PG_PORT)
    POSTGRES_QUERY_FEATURE_TYPES_FOR_MERGE_FILTERS = Yes
    POSTGRES_READ_TIME_WITH_TIMEZONE = Yes
    POSTGRES_SSLMODE = prefer
    POSTGRES_USER_NAME = $(IN_PG_USERNAME)
    SQL_STATEMENT = select * from broken_links.cl_broken_link_problem;
    RESULT -> cl_broken_link_problem (writer XLSXW_1)
cl_broken_link_problem (writer XLSXW_1)
    attributes: problem auto(20), description_en auto(20), description_fr auto(20)
SQLExecutor_4
    COMBINE_ATTRS = Keep Result Attributes if Conflict
    COMBINE_GEOM = Initiator Geometry Only
    DATASET = $(IN_PG_DBNAME)
    EXPOSED_ATTRIBUTE_LIST = metadata_uuid,url,resource_format,broken_link_problem,broken_link_status,broken_link_status_date,juridiction,date_email
    FORMAT = POSTGRES
    POSTGRES_CREATE_FEATURE_TABLES_FROM_DATA = Yes
    POSTGRES_HOST = $(IN_PG_HOST)
    POSTGRES_PASSWORD = $(IN_PG_PWD)
    POSTGRES_PORT = $(IN_PG_PORT)
    POSTGRES_QUERY_FEATURE_TYPES_FOR_MERGE_FILTERS = Yes
    POSTGRES_READ_TIME_WITH_TIMEZONE = Yes
    POSTGRES_SSLMODE = prefer
    POSTGRES_USER_NAME = $(IN_PG_USERNAME)
    SQL_STATEMENT = select * from broken_links.broken_links_issues;
    RESULT -> broken_links_issues (writer XLSXW_1)
broken_links_issues (writer XLSXW_1)
    attributes: metadata_uuid string(200), url string(200), resource_format string(200), broken_link_problem string(200), broken_link_status string(200), broken_link_status_date string(200), juridiction string(200), date_email string(200)
